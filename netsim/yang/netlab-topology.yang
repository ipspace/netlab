module netlab-topology {
  yang-version 1.1;
  namespace "urn:netlab:topology";
  prefix "netlab";

  description
    "YANG model for netlab lab topology validation with MUST statements
     to check internal consistency. The topology is described in a YAML file
     using a dictionary format.";

  revision 2025-12-12 {
    description "Initial version";
  }

  container topology {
    description
      "Network lab topology structure. The three major components that should
       be present in every topology file are: nodes (lab devices), links
       (between the lab devices), and defaults (topology-wide defaults like
       default device type).";

    container defaults {
      description
        "Topology-wide defaults. System defaults are specified in the global
         topology-defaults.yml file and imported into the lab topology under
         the defaults top-level attribute. They can be overwritten with the
         defaults element within the lab topology or from user- or system
         defaults files.";
      leaf device {
        type string;
        description
          "Default device type used for all nodes unless overridden at the
           node level. See supported platforms documentation for available
           device types.";
      }
      leaf provider {
        type string;
        description
          "Virtualization provider (libvirt, clab, or external). Default
           value: libvirt.";
      }
      leaf name {
        type string;
        description
          "Default topology name. If not specified, the first twelve
           characters of the directory name are used (spaces and dots replaced
           with underscores).";
      }
      leaf-list module {
        type string;
        description
          "Default list of optional configuration modules used by this
           network topology. Can be overridden at the node level.";
      }
      // Use anydata for complex nested structures that can have arbitrary keys
      // This allows providers, devices, and other defaults to have flexible structures
      anydata providers {
        description "Provider-specific settings (flexible structure)";
      }
      container sources {
        description
          "Default source files. Source files can be specified in user
           defaults, system defaults, or topology defaults.";
        leaf-list extra {
          type string;
          description "Additional source files to include";
        }
        leaf-list list {
          type string;
          description "List of source files";
        }
        leaf-list user {
          type string;
          description "User source files (from ~/.netlab.yml)";
        }
        leaf-list system {
          type string;
          description "System source files (from /etc/netlab/defaults.yml)";
        }
        anydata other {
          description "Other source settings (flexible structure)";
        }
      }
      anydata devices {
        description "Device-specific default settings (flexible structure)";
      }
      anydata daemons {
        description "Daemon-specific default settings (flexible structure)";
      }
      anydata outputs {
        description "Output module default settings (flexible structure)";
      }
      anydata modules {
        description "Module default settings (flexible structure)";
      }
      anydata attributes {
        description "Attribute validation settings (flexible structure)";
      }
      anydata paths {
        description "Search path settings (flexible structure)";
      }
      anydata tools {
        description "External tools default settings (flexible structure)";
      }
      anydata warnings {
        description "Warning settings (flexible structure)";
      }
      anydata const {
        description "Constants and limits (flexible structure)";
      }
      anydata addressing {
        description "Addressing pool defaults (flexible structure)";
      }
      anydata automation {
        description "Automation settings (flexible structure)";
      }
      anydata hints {
        description "Error hints settings (flexible structure)";
      }
      anydata multilab {
        description "Multi-lab settings (flexible structure)";
      }
      anydata pools {
        description "Address pools (flexible structure)";
      }
      anydata plugin {
        description "Plugin settings (flexible structure)";
      }
      anydata roles {
        description "Role settings (flexible structure)";
      }
      anydata vlan {
        description "VLAN module defaults (flexible structure)";
      }
      anydata ospf {
        description "OSPF module defaults (flexible structure)";
      }
      anydata isis {
        description "ISIS module defaults (flexible structure)";
      }
      anydata evpn {
        description "EVPN module defaults (flexible structure)";
      }
      anydata vrf {
        description "VRF module defaults (flexible structure)";
      }
      anydata sr {
        description "Segment Routing defaults (flexible structure)";
      }
      anydata mpls {
        description "MPLS defaults (flexible structure)";
      }
      anydata srv6 {
        description "SRv6 defaults (flexible structure)";
      }
      anydata bfd {
        description "BFD defaults (flexible structure)";
      }
      anydata gateway {
        description "Gateway defaults (flexible structure)";
      }
      anydata lag {
        description "LAG defaults (flexible structure)";
      }
      anydata vxlan {
        description "VXLAN defaults (flexible structure)";
      }
      anydata netlab {
        description "Netlab-specific defaults (flexible structure)";
      }
      anydata ports {
        description "Port mappings (flexible structure)";
      }
      anydata routing {
        description "Routing policy defaults (flexible structure)";
      }
      anydata ripv2 {
        description "RIP defaults (flexible structure)";
      }
      anydata bgp {
        description "BGP module defaults (flexible structure)";
      }
      anydata dhcp {
        description "DHCP defaults (flexible structure)";
      }
      anydata linux {
        description "Linux defaults (flexible structure)";
      }
      anydata docker {
        description "Docker defaults (flexible structure)";
      }
      anydata ansible {
        description "Ansible defaults (flexible structure)";
      }
      anydata vagrant {
        description "Vagrant defaults (flexible structure)";
      }
      anydata eigrp {
        description "EIGRP defaults (flexible structure)";
      }
      anydata stp {
        description "STP defaults (flexible structure)";
      }
      anydata lldp {
        description "LLDP defaults (flexible structure)";
      }
      anydata ntp {
        description "NTP defaults (flexible structure)";
      }
      anydata snmp {
        description "SNMP defaults (flexible structure)";
      }
      anydata syslog {
        description "Syslog defaults (flexible structure)";
      }
      anydata initial {
        description "Initial configuration defaults (flexible structure)";
      }
      anydata custom_config {
        description "Custom configuration defaults (flexible structure)";
      }
      anydata deploy {
        description "Deployment defaults (flexible structure)";
      }
      anydata prefix {
        description "Prefix defaults (flexible structure)";
      }
      anydata graph {
        description "Graph defaults (flexible structure)";
      }
      anydata report {
        description "Report defaults (flexible structure)";
      }
      // Note: Additional default fields may need to be added as they are encountered
      // YANG doesn't support true catch-all for container children
    }

    list nodes {
      key "name";
      description
        "Lab devices (nodes). Nodes can be specified as a list of strings
         (node names) or a dictionary of node names and node attributes.
         Individual nodes can override the default device type or add
         additional node attributes.";
      
      leaf name {
        type string;
        mandatory true;
        description
          "Node name. Node names can have up to 16 characters by default.
           The maximum length can be changed with defaults.const.MAX_NODE_ID_LENGTH.";
      }
      
      leaf device {
        type string;
        description
          "Device type for this node. If not specified, the default device
           type from defaults.device is used. See supported platforms
           documentation for available device types.";
      }
      
      leaf provider {
        type string;
        description
          "Virtualization provider for this node. Allows mixing providers
           within a single topology (e.g., some nodes using libvirt, others
           using clab).";
      }
      
      leaf box {
        type string;
        description
          "Vagrant box or Docker container identifier. Default images for
           individual device types are defined in system defaults and can be
           changed with defaults.devices... settings.";
      }
      
      leaf id {
        type uint32;
        description
          "Static node identifier (integer between 1 and MAX_NODE_ID, default
           250). If not specified, node ID is assigned based on node's position
           in the nodes dictionary, starting with 1 and skipping static IDs
           used by other nodes.";
      }
      
      leaf role {
        type enumeration {
          enum router {
            description "Router role - device gets loopback IP and participates in routing";
          }
          enum host {
            description "Host role - device does not get loopback IP and uses static routing";
          }
          enum bridge {
            description "Bridge role - device acts as a bridge";
          }
          enum gateway {
            description "Gateway role - device acts as a gateway";
          }
        }
        description
          "Node role. When set to 'host', the device does not get a loopback IP
           address and uses static routing toward the default gateway. Default
           role is 'router'.";
      }
      
      leaf mtu {
        type uint32 {
          range "64..9216";
        }
        description
          "Device-wide (system) MTU. This MTU is applied to all interfaces that
           don't have an explicit MTU. Valid range: 64-9216 bytes.";
      }
      
      anydata loopback {
        description
          "Loopback interface configuration. Can be a boolean 'true' to enable
           loopback, or a dictionary with custom IPv4/IPv6 addresses and other
           loopback settings (flexible structure).";
      }
      
      leaf-list module {
        type string;
        description
          "List of optional configuration modules used by this node. Overrides
           the global module list if specified. Host nodes do not inherit
           global configuration modules.";
      }
      
      list interfaces {
        key "ifindex";
        description
          "Node interfaces. Interfaces are created as needed during the link
           transformation phase and collected in the interfaces list. Each
           interface can have addressing, MTU, and module-specific attributes.";
        leaf ifindex {
          type uint32;
          description
            "Interface index used to generate the interface/port name. Can be
             specified per-node in link definitions with the ifindex attribute.";
        }
        anydata interface_data {
          description
            "Interface data including addressing, MTU, module-specific
             attributes, and other interface parameters (flexible structure)";
        }
      }
      
      anydata clab {
        description
          "Containerlab-specific node settings. Can include attributes like
           clab.type (device type when supported by containerlab) and
           clab.license (license file needed for network devices).";
      }
      anydata libvirt {
        description
          "Libvirt-specific node settings. Can include attributes like
           libvirt.nic_model (virtual NIC model: virtio, e1000, rtl8139, etc.).";
      }
      anydata external {
        description
          "External provider-specific node settings. Used when integrating
           netlab topologies with external devices or management systems.";
      }
      
      // Device-specific attributes (eos, frr, ios, etc.)
      anydata eos {
        description
          "Arista EOS-specific node attributes (e.g., eos.systemmacaddr, eos.serialnumber).";
      }
      anydata frr {
        description
          "FRR-specific node attributes.";
      }
      anydata ios {
        description
          "Cisco IOS-specific node attributes.";
      }
      // Add other device-specific attributes as needed
      
      // Module-specific attributes (routing, bgp, ospf, etc.)
      anydata routing {
        description
          "Routing module node attributes (e.g., routing.static for static routes).";
      }
      anydata bridge {
        description
          "Bridge module node attributes.";
      }
      anydata dhcp {
        description
          "DHCP module node attributes.";
      }
      // Add other module-specific attributes as needed

      
      container bgp {
        when "../module[.='bgp']";
        description
          "BGP configuration. This container can only be present when the BGP
           module is enabled on the node.";
        must "../module[.='bgp']" {
          error-message "BGP container can only be present when BGP module is enabled";
        }
        leaf as {
          type uint32;
          mandatory true;
          description
            "BGP AS number. Nodes with the same AS number are automatically
             grouped into an AS group (e.g., as65000).";
        }
      }
      
      must "device or ../../defaults/device" {
        error-message "Node must have a device type or a default device must be set";
      }
    }

    list links {
      description
        "Links between lab devices. Links can be specified in multiple
         formats: as a string (node-node format), as a list of node names
         (for multi-access links), as a dictionary of node names and link
         attributes, or as a dictionary with a list of node interfaces.
         Each link definition is converted into a dictionary+list of
         interfaces format during topology transformation.";
      key "linkindex";
      
      leaf linkindex {
        type uint32;
        description
          "Link sequence number (starting with one), used to generate default
           bridge names in libvirt. This is a read-only attribute set during
           topology transformation.";
      }
      
      list interfaces {
        key "node";
        description
          "Interfaces connected by this link. Each interface entry represents
           a node attachment to the link.";
        min-elements 1;
        
        leaf node {
          type leafref {
            path "../../../nodes/name";
            require-instance true;
          }
          mandatory true;
          description
            "Node name. Must reference a node defined in the nodes list.";
        }
        
        leaf ipv4 {
          type union {
            type boolean;
            type string;
          }
          description
            "IPv4 address for this interface. Can be specified as an address
             string or as a boolean 'true' for unnumbered interfaces (where
             the interface uses the node's loopback address).";
        }
        
        leaf ipv6 {
          type union {
            type boolean;
            type string;
          }
          description
            "IPv6 address for this interface. Can be specified as an address
             string or as a boolean 'true' for unnumbered interfaces (where
             the interface uses the node's loopback address).";
        }
        
        leaf shutdown {
          type boolean;
          description
            "Shut down this interface during initial configuration.";
        }
        
        leaf mtu {
          type uint32 {
            range "64..9216";
          }
          description
            "Interface MTU. Valid range: 64-9216 bytes.";
        }
        
        anydata interface_attrs {
          description
            "Additional interface attributes (flexible structure)";
        }
      }
      
      leaf bandwidth {
        type uint32;
        description
          "Link bandwidth in Mbps. Used to configure interface bandwidth
           when supported by the connected device(s).";
      }
      
      leaf type {
        type enumeration {
          enum p2p {
            description "Point-to-point link between two nodes";
          }
          enum lan {
            description "Multi-access link (LAN)";
          }
          enum stub {
            description "Stub link (single node attachment)";
          }
          enum loopback {
            description "Loopback link";
          }
          enum tunnel {
            description "Tunnel link";
          }
          enum vlan_member {
            description "VLAN member link";
          }
          enum lag {
            description "Link aggregation group (LAG)";
          }
        }
        description
          "Link type. Valid values: p2p (point-to-point), lan (multi-access),
           stub (single node attachment), loopback, tunnel, vlan_member, lag.
           When missing, link type is selected based on the number of devices
           connected to the link.";
      }
      
      leaf bridge {
        type string;
        description
          "Bridge name for this link. Used in libvirt provider to specify
           the Linux bridge name for the link.";
      }
      
      leaf pool {
        type string;
        description
          "Address pool name to use for this link. References a pool defined
           in the addressing element.";
      }
      
      leaf prefix {
        type string;
        description
          "Prefix name to use for this link. References a prefix defined
           in the prefix element.";
      }
      
      leaf name {
        type string;
        description
          "Link name. Used for identification and in some provider configurations.";
      }
      
      leaf mtu {
        type uint32 {
          range "64..9216";
        }
        description
          "Link MTU. Valid range: 64-9216 bytes.";
      }
      
      container ra {
        description
          "IPv6 Router Advertisement (RA) configuration for this link.";
        leaf disable {
          type boolean;
          description
            "Disable Router Advertisements on this link.";
        }
        leaf slaac {
          type boolean;
          description
            "Enable Stateless Address Autoconfiguration (SLAAC).";
        }
        leaf dhcp {
          type string;
          description
            "DHCP configuration: 'all' or 'other'.";
        }
        leaf onlink {
          type boolean;
          description
            "Advertise on-link prefix.";
        }
        anydata ra_config {
          description
            "Additional RA configuration attributes (flexible structure)";
        }
      }
      
      anydata link_attrs {
        description
          "Additional link attributes (flexible structure)";
      }
      
      must "count(interfaces/node) >= 2 or type = 'stub' or type = 'loopback' or not(type)" {
        error-message "Link must connect at least two nodes (unless it's a stub or loopback link, or type is not specified)";
      }
    }

    leaf-list module {
      type string;
      description
        "Default list of optional configuration modules used by this network
         topology. You can use device-level module attribute to override this
         setting for individual nodes. Host nodes do not inherit global
         configuration modules.";
    }
    
    leaf message {
      type string;
      description
        "Help message to display after successful 'netlab initial' or
         'netlab up' commands. You can use this message to tell the end-user
         how to use the lab.";
    }
    
    leaf name {
      type string;
      description
        "Topology name used to name Linux bridges when using libvirt Vagrant
         plugin. If not specified, the first twelve characters of the directory
         name are used (spaces and dots replaced with underscores).";
    }
    
    leaf provider {
      type string;
      description
        "Virtualization provider (libvirt, clab, or external). Default value:
         libvirt.";
    }
    
    leaf version {
      type string;
      description
        "Minimum netlab version required to use this lab topology. You can
         use either a simple version number or Python module version
         specification (example: >= 1.6.3).";
    }
    
    anydata addressing {
      description
        "IPv4 and IPv6 address pools used to address management, loopback,
         LAN, P2P and stub interfaces. Default pools include: mgmt (management
         addresses), loopback (loopback addresses), lan (LAN link addresses),
         p2p (point-to-point link addresses), and others. You can override or
         augment them in the topology addressing element.";
    }
    
    anydata pools {
      description
        "Address pools (internal representation, flexible structure). This
         is the processed form of the addressing element after topology
         transformation.";
    }
    
    anydata groups {
      description
        "Groups of lab objects (nodes, VLANs, or VRFs) with similar
         attributes. Groups are specified as a dictionary with group names
         as keys. Dictionary values can be either a list of member nodes or a
         dictionary specifying members. Groups can be used to set node/VLAN/VRF
         attributes, set Ansible group variables, or limit the scope of netlab
         commands.";
    }
    
    anydata vlans {
      description
        "VLAN definitions. VLANs are specified as a dictionary with VLAN
         names as keys. Each VLAN can have attributes like mode (bridge, irb,
         route), links (list of links associated with the VLAN), and other
         VLAN-specific settings.";
    }
    
    anydata validate {
      description
        "Lab validation tests. Validation tests are specified as a dictionary
         with test names as keys. Each test can define nodes to test, wait
         conditions, plugins to execute, and expected results.";
    }
    
    anydata prefix {
      description
        "Named IP prefixes that can be used to address links and VLANs or in
         prefix lists or validation expressions. The dictionary keys are
         prefix names (e.g., lan_1, lan_2, loopback); the values are dictionaries
         defining individual prefixes with ipv4, ipv6, pool, and allocation
         attributes (flexible structure).";
    }
    
    container tools {
      description
        "External network management tools deployed after the lab has been
         started and configured. Tools are started as Docker containers and
         can access the management network and management interfaces of lab
         devices.";
      anydata tool_definitions {
        description
          "Tool definitions. Each tool can have runtime, enabled, and
           tool-specific configuration parameters (flexible structure)";
      }
    }
    
    leaf-list plugin {
      type string;
      description
        "List of plugins used by this topology. Plugins extend netlab
         functionality with custom configuration templates, validation tests,
         or other features.";
    }
    
    anydata Plugin {
      description
        "Plugin internal data (flexible structure). Internal representation
         of plugin configuration after topology transformation.";
    }
    
    anydata Provider {
      description
        "Provider internal data (flexible structure). Internal representation
         of provider configuration after topology transformation.";
    }
    
    anydata libvirt {
      description
        "Libvirt-specific topology settings. Can include libvirt-specific
         configuration like bridge names, port mappings, and other
         virtualization provider settings.";
    }
    
    anydata clab {
      description
        "Containerlab-specific topology settings. Can include containerlab-specific
         configuration like network names, container settings, and other
         containerlab provider settings.";
    }
    
    leaf-list input {
      type string;
      description
        "Input topology file paths (internal). Tracks the source topology
         files used during transformation.";
    }
    
    // Global MUST statements
    must "count(nodes) > 0" {
      error-message "Topology must contain at least one node";
    }
  }
}
